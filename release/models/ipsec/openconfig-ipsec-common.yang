submodule openconfig-ipsec-common {
  belongs-to "openconfig-ipsec" {
    prefix "oc-ipsec";
  }

  import openconfig-interfaces { prefix "oc-if"; }
  import openconfig-extensions { prefix "oc-ext"; }
  import openconfig-yang-types { prefix "oc-yang"; }
  import openconfig-inet-types { prefix "oc-inet"; }

  // meta
  organization "OpenConfig working group";

  contact
    "OpenConfig working group
    netopenconfig@googlegroups.com";

  description
    "Model for managing IPsec.

    This model reuses data items defined in the IETF YANG model for
    interfaces described by RFC 7223 with an alternate structure
    (particularly for operational state data) and with
    additional configuration items.

    Portions of this code were derived from IETF RFC 7223.
    Please reproduce this note if possible.

    IETF code is subject to the following copyright and license:
    Copyright (c) IETF Trust and the persons identified as authors of
    the code.
    All rights reserved.

    Redistribution and use in source and binary forms, with or without
    modification, is permitted pursuant to, and subject to the license
    terms contained in, the Simplified BSD License set forth in
    Section 4.c of the IETF Trust's Legal Provisions Relating
    to IETF Documents (http://trustee.ietf.org/license-info).";


  revision "2022-08-05" {
    description
      "Intial Version";
    reference "1.1.0";
  }

  typedef ipsec-traffic-direction {
    type enumeration {
      enum inbound {
        description "Inbound traffic.";
      }
      enum outbound {
        description "Outbound traffic.";
      }
    }
    description
      "IPsec traffic direction is defined in two
      directions: inbound and outbound. From a NSF
      perspective inbound means the traffic that enters
      the NSF and outbound is the traffic that is sent
      from the NSF.";
    reference
      "Section 5 in RFC 4301.";
  }
   typedef ipsec-mode {
    type enumeration {
      enum transport {
        description
          "IPsec transport mode. No Network Address
          Translation (NAT) support.";
        }
      enum tunnel {
        description "IPsec tunnel mode.";
      }
    }
    description
      "Type definition of IPsec mode: transport or
      tunnel.";
    reference
      "Section 3.2 in RFC 4301.";
  }

  typedef ipsec-protocol-parameters {
    type enumeration {
      enum esp { description "IPsec ESP protocol."; }
    }
    description
      "Only the Encapsulation Security Protocol (ESP) is
      supported but it could be extended in the future.";
    reference
      "RFC 4303- IP Encapsulating Security Payload
      (ESP).";
  }
  typedef encryption-algorithm-type {
    type uint16;
    description
      "The encryption algorithm is specified with a 16-bit
      number extracted from IANA Registry. The acceptable
      values MUST follow the requirement levels for
      encryption algorithms for ESP and IKEv2.";
    reference
      "IANA; Internet Key Exchange V2 (IKEv2) Parameters;
      Transform Atribute Types; Transform Type 1 - Encryption
      Algorithm Transform IDs. RFC 8221 - Cryptographic
      Algorithm Implementation Requirements and Usage
      Guidance for Encapsulating Security Payload (ESP)
      and Authentication Header (AH) and RFC 8247 -
      Algorithm Implementation Requirements and Usage
      Guidance for the Internet Key Exchange Protocol
      Version 2 (IKEv2).";
  }

  typedef integrity-algorithm-type {
    type uint16;
    description
      "The integrity algorithm is specified with a 16-bit
      number extracted from IANA Registry.
      The acceptable values MUST follow the requirement
      levels for encryption algorithms for ESP and IKEv2.";
    reference
      "IANA; Internet Key Exchange V2 (IKEv2) Parameters;
      Transform Atribute Types; Transform Type 3 - Integrity
      Algorithm Transform IDs. RFC 8221 - Cryptographic
      Algorithm Implementation Requirements and Usage
      Guidance for Encapsulating Security Payload (ESP)
      and Authentication Header (AH) and RFC 8247 -
      Algorithm Implementation Requirements and Usage
      Guidance for the Internet Key Exchange Protocol
      Version 2 (IKEv2).";
  }

  grouping lifetime {
    description
      "Different lifetime values limited to an IPsec SA.";
    leaf time {
      type uint32;
      units "seconds";
      default 0;
      description
        "Time in seconds since the IPsec SA was added.
        For example, if this value is 180 seconds it
        means the IPsec SA expires in 180 seconds since
        it was added. The value 0 implies infinite.";
    }
    leaf bytes {
      type uint32;
      default 0;
      description
         "If the IPsec SA processes the number of bytes
         expressed in this leaf, the IPsec SA expires and
         should be rekeyed. The value 0 implies
         infinite.";
    }
    leaf packets {
      type uint32;
      default 0;
      description
         "If the IPsec SA processes the number of packets
         expressed in this leaf, the IPsec SA expires and
         should be rekeyed. The value 0 implies
         infinite.";
    }
    leaf idle {
      type uint32;
      units "seconds";
      default 0;
      description
        "When a NSF stores an IPsec SA, it
        consumes system resources. In an idle NSF this
        is a waste of resources. If the IPsec SA is idle
        during this number of seconds the IPsec SA
        should be removed. The value 0 implies
        infinite.";
    }
    reference
      "Section 4.4.2.1 in RFC 4301.";
  }
  
  typedef lifetime-action {
    type enumeration {
      enum terminate-clear {
        description
          "Terminates the IPsec SA and allows the
          packets through.";
      }
      enum terminate-hold {
        description
          "Terminates the IPsec SA and drops the
          packets.";
      }
      enum replace  {
        description
          "Replaces the IPsec SA with a new one:
          rekey. ";
      }
    }
    description
      "When the lifetime of an IPsec SA expires an action
      needs to be performed over the IPsec SA that
      reached the lifetime. There are three posible
      options: terminate-clear, terminate-hold and
      replace.";
    reference
      "Section 4.5 in RFC 4301.";
  }  

  grouping tunnel-grouping {
    description
      "The parameters required to define the IP tunnel
      endpoints when IPsec SA requires tunnel mode. The
      tunnel is defined by two endpoints: the local IP
      address and the remote IP address.";

    leaf local {
      type oc-inet:ip-address;
        mandatory true;
        description
          "Local IP address' tunnel endpoint.";
    }
    leaf remote {
      type oc-inet:ip-address;
      mandatory true;
      description
        "Remote IP address' tunnel endpoint.";
    }
    leaf df-bit {
      type enumeration {
        enum clear {
          description
            "Disable the DF (Don't Fragment) bit
            from the outer header. This is the
            default value.";
        }
        enum set {
          description
            "Enable the DF bit in the outer header.";
        }
        enum copy {
          description
            "Copy the DF bit to the outer header.";
        }
      }
      default clear;
      description
        "Allow configuring the DF bit when encapsulating
        tunnel mode IPsec traffic. RFC 4301 describes
        three options to handle the DF bit during
        tunnel encapsulation: clear, set and copy from
        the inner IP header.";
      reference
        "Section 8.1 in RFC 4301.";
    }
    leaf bypass-dscp {
      type boolean;
      default true;
      description
        "If DSCP (Differentiated Services Code Point)
        values in the inner header have to be used to
        select one IPsec SA among several that match
        the traffic selectors for an outbound packet";
      reference
        "Section 4.4.2.1. in RFC 4301.";
    }
    leaf-list dscp-mapping {
      type oc-inet:dscp;
      default 0;
      description
        "DSCP values allowed for packets carried over
        this IPsec SA.";
      reference
        "Section 4.4.2.1. in RFC 4301.";
    }
    leaf ecn {
      type boolean;
      default false;
      description
        "Explicit Congestion Notification (ECN). If true
        copy CE bits to inner header.";
      reference
        "Section 5.1.2 and Appendix C in RFC 4301.";
    }
  }
  typedef esp-encap {
    type enumeration {
      enum espintcp {
        description
          "ESP in TCP encapsulation.";
        reference
          "RFC 8229 - TCP Encapsulation of IKE and
          IPsec Packets.";
        }
      enum espintls {
        description
          "ESP in TCP encapsulation using TLS.";
        reference
          "RFC 8229 - TCP Encapsulation of IKE and
          IPsec Packets.";
      }
      enum espinudp {
        description
          "ESP in UDP encapsulation.";
        reference
          "RFC 3948 - UDP Encapsulation of IPsec ESP
          Packets.";
      }
      enum none {
        description
          "NOT ESP encapsulation.";
      }
    }
    description
      "Types of ESP encapsulation when Network Address
      Translation (NAT) is present between two NSFs.";
    reference
      "RFC 8229 - TCP Encapsulation of IKE and IPsec
      Packets and RFC 3948 - UDP Encapsulation of IPsec
      ESP Packets.";
  }

  typedef ipsec-spd-action {
    type enumeration {
      enum protect {
        description
          "PROTECT the traffic with IPsec.";
      }
      enum bypass {
        description
          "BYPASS the traffic. The packet is forwarded
          without IPsec protection.";
      }
      enum discard {
        description
          "DISCARD the traffic. The IP packet is
          discarded.";
      }
    }
    description
      "The action when traffic matches an IPsec security
      policy. According to RFC 4301 there are three
      possible values: BYPASS, PROTECT AND DISCARD";
    reference
      "Section 4.4.1 in RFC 4301.";
  }

  typedef ipsec-inner-protocol {    //TODO: this might be there ?
    type union {
      type uint8;
      type enumeration {
        enum any {
          value 256;
          description
            "Any IP protocol number value.";
        }
      }
    }
    default any;
    description
      "IPsec protection can be applied to specific IP
      traffic and layer 4 traffic (TCP, UDP, SCTP, etc.)
      or ANY protocol in the IP packet payload. We
      specify the IP protocol number with an uint8 or
      ANY defining an enumerate with value 256 to
      indicate the protocol number. NOTE: In case
      of IPv6, the protocol in the IP packet payload
      is specified in the Next Header field of the IPv6
      packet.";
    reference
      "Section 4.4.1.1 in RFC 4301.
      IANA Registry - Protocol Numbers.";
  }
  grouping port-range  {
    description
      "This grouping defines a port range, such as
      expressed in RFC 4301. For example: 1500 (Start
      Port Number)-1600 (End Port Number).
      A port range is used in the Traffic Selector.";

    leaf start {
      type oc-inet:port-number;
      description "Start port number.";
    }
    leaf end {
      type oc-inet:port-number;
      must '. >= ../start' {
        error-message
          "The end port number MUST be equal or greater
          than the start port number.";
      }
      description
        "End port number. To express a single port, set
        the same value as start and end.";
    }
    reference "Section 4.4.1.2 in RFC 4301.";
  }

  grouping encap {
    description
      "This group of nodes allows to define the type of
      encapsulation in case NAT traversal is
      required and port information.";
    leaf espencap {
      type esp-encap;
      default none;
      description
        "ESP in TCP, ESP in UDP or ESP in TLS.";
    }
    leaf sport {
      type oc-inet:port-number;
      default 4500;
      description
        "Encapsulation source port.";
    }
    leaf dport {
      type oc-inet:port-number;
      default 4500;
      description
        "Encapsulation destination port.";
    }

    leaf-list oaddr {
      type oc-inet:ip-address;
      description
        "If required, this is the original address that
        was used before NAT was applied over the Packet.
        ";
    }
    reference
      "RFC 3947 and RFC 8229.";
  }

  grouping selector-grouping {
    description
      "This grouping contains the definition of a Traffic
      Selector, which is used in the IPsec policies and
      IPsec SAs.";

    leaf local-subnet { //TODO: IP's also shouild have range + union of subnet
      type oc-inet:ip-prefix;
      mandatory true;
      description
        "Local IP address subnet.";
    }
    leaf remote-subnet {
      type oc-inet:ip-prefix;
      mandatory true;
      description
        "Remote IP address subnet.";
    }
    leaf inner-protocol {
      type ipsec-inner-protocol;
      default any;    // TODO: how this can be used for ports
      description
        "Inner Protocol that is going to be
        protected with IPsec.";
    }
    list local-ports {
      key "start end";
      uses port-range;
      description
        "List of local ports. When the inner
        protocol is ICMP this 16 bit value
        represents code and type.
        If this list is not defined
        it is assumed that start and
        end are 0 by default (any port).";
    }
    list remote-ports {
      key "start end";
      uses port-range;
      description
        "List of remote ports. When the upper layer
        protocol is ICMP this 16 bit value represents
        code and type.If this list is not defined
        it is assumed that start and end are 0 by
        default (any port)";
    }
    reference
      "Section 4.4.1.2 in RFC 4301.";
  }
  grouping ipsec-policy-grouping {
    description
      "Holds configuration information for an IPsec SPD
      entry.";

    leaf anti-replay-window { //TODO: check rfc to see if this is only for ike
      type uint64;
      default 32;
      description
        "A 64-bit counter used to determine whether an
        inbound ESP packet is a replay.";
      reference
        "Section 4.4.2.1 in RFC 4301.";
    }
    container traffic-selector {
      description
        "Packets are selected for
        processing actions based on the IP and inner
        protocol header information, selectors,
        matched against entries in the SPD.";
        uses selector-grouping;
      reference
        "Section 4.4.4.1 in RFC 4301.";
    }
    container processing-info {
      description
        "SPD processing. If the required processing
        action is protect, it contains the required
        information to process the packet.";
      leaf action {
        type ipsec-spd-action;
        default discard;
        description
          "If bypass or discard, container
          ipsec-sa-cfg is empty.";
      }
      container ipsec-sa-cfg {
        when "../action = 'protect'";
        description
          "IPsec SA configuration included in the SPD
          entry.";
        leaf pfp-flag {
           type boolean;
           default false;
           description
             "Each selector has a Populate From
             Packet (PFP) flag. If asserted for a
             given selector X, the flag indicates
             that the IPsec SA to be created should
             take its value (local IP address,
             remote IP address, Next Layer
             Protocol, etc.) for X from the value
             in the packet. Otherwise, the IPsec SA
             should take its value(s) for X from
             the value(s) in the SPD entry.";
        }
        leaf ext-seq-num { //TODO: looks like only needed for IKE
          type boolean;
          default false;
          description
            "True if this IPsec SA is using extended
            sequence numbers. True 64 bit counter,
            False 32 bit.";
        }
        leaf seq-overflow {
          type boolean;
          default false;
          description
            "The flag indicating whether
            overflow of the sequence number
            counter should prevent transmission
            of additional packets on the IPsec
            SA (false) and, therefore needs to
            be rekeyed, or whether rollover is
            permitted (true). If Authenticated
            Encryption with Associated Data
            (AEAD) is used (leaf
            esp-algorithms/encryption/algorithm-type)
            this flag MUST be false.";
        }
        leaf stateful-frag-check {
          type boolean;
          default false;
          description
            "Indicates whether (true) or not (false)
            stateful fragment checking applies to
            the IPsec SA to be created.";
        }
        leaf mode {
          type ipsec-mode;
          default transport;
          description
            "IPsec SA has to be processed in
            transport or tunnel mode.";
        }
        leaf protocol-parameters {
          type ipsec-protocol-parameters;
          default esp;
          description
            "Security protocol of the IPsec SA:
            Only ESP is supported but it could be
            extended in the future.";
        }
        container esp-algorithms {
          when "../protocol-parameters = 'esp'";
          description
            "Configuration of Encapsulating
            Security Payload (ESP) parameters and
            algorithms.";

          leaf-list integrity {
            type integrity-algorithm-type;
              default 0;
              ordered-by user;
              description
                "Configuration of ESP authentication
                based on the specified integrity
                algorithm. With AEAD algorithms,
                the integrity node is not used.";
              reference
                "Section 3.2 in RFC 4303.";
          }
          list encryption {
            key id;
            ordered-by user;
            leaf id {
              type uint8;
              description
                "The index of list with the
                different encryption algorithms and
                its key-length (if required).";
            }
            leaf algorithm-type {
              type oc-ipsec:encryption-algorithm-type;
              default 20;
              description
                "Default value 20 (ENCR_AES_GCM_16)";
            }
            leaf key-length {
              type uint16;
              default 128;
              description
                "By default key length is 128
                bits";
            }
            description
              "Encryption or AEAD algorithm for the
              IPsec SAs. This list is ordered
              following from the higher priority to
              lower priority. First node of the
              list will be the algorithm with
              higher priority. In case the list
              is empty, then
              no encryption algorithm
              is applied (NULL).";
            reference
              "Section 3.2 in RFC 4303.";
          }
          leaf tfc-pad {
            type boolean;
            default false;
            description
              "If Traffic Flow Confidentiality
              (TFC) padding for ESP encryption
              can be used (true) or not (false)";
            reference
              "Section 2.7 in RFC 4303.";
          }
          reference
            "RFC 4303.";
        }
        container tunnel {
          when "../mode = 'tunnel'";
          uses tunnel-grouping;
          description
            "IPsec tunnel endpoints definition.";
        }
      } //ipsec-sa-cfg 
      reference
        "Section 4.4.1.2 in RFC 4301.";
    }
    container spd-mark {
      description
        "The Mark to set for the IPsec SA of this
        connection. This option is only available
        on linux NETKEY/XFRM kernels. It can be
        used with iptables to create custom
        iptables rules using CONNMARK. It can also
        be used with Virtual Tunnel Interfaces
        (VTI) to direct marked traffic to
        specific vtiXX devices.";

      leaf mark {
        type uint32;
        default 0;
        description
          "Mark used to match XFRM policies and
          states.";
      }
      leaf mask {
        type uint32;
        default 0;
        description
          "Mask used to match XFRM policies and
          states.";
      }
    }
  }

}
